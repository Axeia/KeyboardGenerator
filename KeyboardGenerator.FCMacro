__Name__            = 'Keyboard Generator'
__Comment__         = 'Generates a keyboard from a keyboard-layout-editor.com layout'
__Author__          = 'Axeia'
__Version__         = '0.1.0 Alpha' 
__Date__            = ''
__License__         = 'MIT'
__Web__             = ''
__Wiki__            = ''
__Icon__            = 'KeyboardGenerator/kg-logo/kg-logo.svg'
__Help__            = ''
__Status__          = 'Alpha'
__Requires__        = 'FreeCAD >= v0.20'
__Communication__   = 'https://forum.freecad.org/memberlist.php?mode=viewprofile&u=54199'
__Files__           = 'KeyboardGenerator/Dialog.py,KeyboardGenerator/FreeCADKeyboard.py,KeyboardGenerator/Key.py,KeyboardGenerator/keyboard-info.html,KeyboardGenerator/KeyboardQ.py,KeyboardGenerator/kg-logo.json,KeyboardGenerator/kg-logo.svg,KeyboardGenerator/LICENSE.txt,KeyboardGenerator/SvgKeyboard.py,KeyboardGenerator/SvgPlateThickness.py,KeyboardGenerator/icons/corner_angled.svg,KeyboardGenerator/icons/corner_right_angle.svg,KeyboardGenerator/icons/corner_rounded.svg,KeyboardGenerator/icons/error.svg,KeyboardGenerator/icons/questionmark.svg,KeyboardGenerator/kg-logo/kg-logo.svg,KeyboardGenerator/pykle_serial/LICENSE.txt,KeyboardGenerator/pykle_serial/serial.py,KeyboardGenerator/svgs/key-spacing.svg,KeyboardGenerator/svgs/mouse-left-click.svg,KeyboardGenerator/svgs/mouse-right-click.svg,KeyboardGenerator/svgs/plate-thickness.svg,KeyboardGenerator/svgs/stabilizer-alps.svg,KeyboardGenerator/svgs/stabilizer-cherry+costar.svg,KeyboardGenerator/svgs/stabilizer-cherry-legend.svg,KeyboardGenerator/svgs/stabilizer-cherry-spec.svg,KeyboardGenerator/svgs/stabilizer-cherry.svg,KeyboardGenerator/svgs/stabilizer-costar.svg,KeyboardGenerator/svgs/switch-alps.svg,KeyboardGenerator/svgs/switch-cherry+alps.svg,KeyboardGenerator/svgs/switch-cherry-openable.svg,KeyboardGenerator/svgs/switch-cherry.svg'
# If you have added or removed any files to this macro please run this file
# directly as a python file (not through FreeCAD) and it will create a new
# __FILES__ variable in the console for you to paste above

import os
absPath = os.path.abspath(os.path.dirname(__file__))
absPathCharCount = len(absPath)
__KeyboardGeneratorPath__ =  absPath + os.path.sep + 'KeyboardGenerator' + os.path.sep

def excludeFile(fileName: str) -> bool:
    blacklistedExtensions = ['.git', '.json5']
    blacklistedDirectories = [os.path.sep + '__pycache__' + os.path.sep]

    for blacklistedExtension in blacklistedExtensions:
        if fileName.endswith(blacklistedExtension):
            return True
    for blacklistedDirectory in blacklistedDirectories:
        if blacklistedDirectory in fileName:
            return True

    return False

def create__Files__string():
    filesVar = "__Files__           = '"
    for path, subDirs, fileNames in os.walk(__KeyboardGeneratorPath__):
        for fileName in fileNames:
            filePath = os.path.join(path, fileName)
            if not excludeFile(filePath):
                filesVar += f'{filePath.lstrip(absPath)},'.replace(os.path.sep, '/')

    filesVar = filesVar.rstrip(',')
    filesVar += "'"

    return filesVar 


try:
    import FreeCAD
    isRunningDirectly = False
except:
    isRunningDirectly = True

if isRunningDirectly:
    print(create__Files__string())
else:
    import sys
    sys.path.append(__KeyboardGeneratorPath__)
    userJSONFile = __KeyboardGeneratorPath__ + 'last-keyboard.json5'
    import Dialog
    from importlib import reload
    reload(Dialog)
    d = Dialog.UiDialog(__Name__, __Version__, userJSONFile)  # Extends QDialog
    d.show()
